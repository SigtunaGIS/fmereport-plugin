FME workspace Example_report.fmw

Parameters:
- PARAMETER = POINT(138396.4 6612885.810000001)   # Geometri Origo
- SourceDataset_CSV2 = $(FME_MF_DIR)tabelldata.csv   # Source CSV (Comma Separated Value) File(s)
- DestDataset_TEXTLINE = C:\Projekt\Sigtuna\Byggrapport.json   # Destination Text File
- GEOM = POINT(138396.4 6612885.810000001)   # Geometri Origo
- LAYER =   # Lagernamn för lager som används för välj objekt
- GID = 77   # GID of object from pick layer

Readers:
- CSV2_1: CSV2 from $(SourceDataset_CSV2)

Writers:
- TEXTLINE_1: TEXTLINE to $(DestDataset_TEXTLINE)

Bookmark: Geometrilös datakälla
CSV (reader CSV2_1)
    attributes: fornamn varchar(10), efternamn varchar(10), e-post varchar(27), kon varchar(1), adress varchar(16), fodd uint32, uuid varchar(1), fnr uint32, adrplstatus uint32, adressplats uint32, adressnamn varchar(13), adressnummer uint32, beladress varchar(16), postnr varchar(6), postort varchar(7), popnamn varchar(12), fastighet varchar(11), skommundel varchar(7), xkoords x_coordinate, ykoords y_coordinate
    -> VertexCreator
VertexCreator
    MEASURE_TYPE = Continuous
    MODE_NAME = Replace with Point
    XVAL = @Value(ykoords)
    YVAL = @Value(xkoords)
    -> CoordinateSystemSetter
CoordinateSystemSetter
    COORDSYS = SWEREF-99-18-00
    -> SpatialFilter_3 [Candidate]

Bookmark: Hämtar geometri ritad i Origo
Creator_2
    GEOMTYPE = Geometry Object
    NUM = 1
    CREATED -> ParameterFetcher
ParameterFetcher
    ATTR_LIST = _paramGeom $(GEOM) _layerName $(LAYER) _layerGid $(GID)
    -> Tester
Tester
    BOOL_OP = OR
    TEST_CLAUSE = TEST _layerName NOT_ATTRIBUTE_HAS_A_VALUE ""
    TEST_MODE = TEST
    PASSED -> GeometryReplacer
    FAILED -> FeatureReader_4 [INITIATOR]
GeometryReplacer
    KIND_LONG = OGC Well Known Text
    OGC_WKT_PRECISION_DISPLAY = 64-bit
    REMOVE_ATTRIBUTE = Yes
    SOURCE = @Value(_paramGeom)
    -> Clipper [CLIPPER]
    -> SpatialFilter_3 [Filter]
    -> FeatureReader_2 [INITIATOR]
    -> ParameterFetcher_2
Note: Används för "Välj geometri" funktionen. / Hämtar aktuell geometri genom att läsa in lager LAYER och matcha på nyckel GID
FeatureReader_4
    ATTR_ACCUM_MODE = Only Use Result
    COMBINE_GEOM = Use Result
    DATASET = localhost
    FEATURETYPES = drk.$(LAYER)
    FORMAT = POSTGIS
    INTERACT = NONE
    ORDER_RESULTS = No
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = localhost
    POSTGIS_QUERY_FEATURE_TYPES_FOR_MERGE_FILTERS = Yes
    POSTGIS_READ_TIME_WITH_TIMEZONE = Yes
    POSTGIS_SCHEMAS_FOR_TABLE_LISTING = drk
    POSTGIS_USE_SEARCH_ENVELOPE = NO
    POSTGIS_USE_TRUE_POSTGIS_TYPES = yes
    WHERE = gid = $(GID)
    <OTHER> -> SpatialFilter_3 [Filter]
    <OTHER> -> FeatureReader_2 [INITIATOR]
    <OTHER> -> ParameterFetcher_2

Bookmark: Filtrering och inläsning
Note: Excel-data
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_6
Note: Adresser
FeatureReader_2
    ATTRIBUTES = gis.fir_adress_p,"uuid,beladress,postnr,postort,popnamn,fastighet,xkoords,ykoords,gid"
    ATTR_ACCUM_MODE = Only Use Result
    COMBINE_GEOM = Use Result
    DATASET = $(FME_MF_DIR)gis.fir_adress_p.shp
    FORMAT = SHAPEFILE
    INTERACT = INTERSECTS
    ORDER_RESULTS = No
    OUTPUT_FEATURES_DISPLAY = Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    gis.fir_adress_p -> AttributeExposer_2

Bookmark: Sätter attribut för utskrift
Note: Folkbokförda sammanställs för området
Note: fme_feature_name är samma som geoservernamn i vår geoserver
AttributeCreator_6
    ATTR_TABLE:
      SET_TO Ålder (varchar(200)) = @sub(@DateTimeFormat(@DateTimeNow(),	%Y),@Value(fodd))
      SET_TO Åldersgrupp (varchar(200)) = FME_CONDITIONAL:DEFAULT_VALUE'_FME_NO_OP_'BOOL_OP;OR;COMPOSITE_TEST;1;TEST @Value(Ålder) < 5'0-5'BOOL_OP;AND;COMPOSITE_TEST;1 AND 2;TEST @Value(Ålder) >= 5;TEST @Value(Ålder) < 15'5-15'BOOL_OP;AND;COMPOSITE_TEST;1 AND 2;TEST @Value(Ålder) >= 15;TEST @Value(Ålder) < 25'15-25'BOOL_OP;AND;COMPOSITE_TEST;1 AND 2;TEST @Value(Ålder) >= 25;TEST @Value(Ålder) < 35'25-35'BOOL_OP;AND;COMPOSITE_TEST;1 AND 2;TEST @Value(Ålder) >= 35;TEST @Value(Ålder) < 45'35-45'BOOL_OP;AND;COMPOSITE_TEST;1 AND 2;TEST @Value(Ålder) >= 45;TEST @Value(Ålder) < 55'45-55'BOOL_OP;AND;COMPOSITE_TEST;1 AND 2;TEST @Value(Ålder) >= 55;TEST @Value(Ålder) < 65'55-65'BOOL_OP;OR;COMPOSITE_TEST;1;TEST @Value(Ålder) >= 65'65+'FME_NUM_CONDITIONS9___
      SET_TO 0-5 (varchar(200)) = FME_CONDITIONAL:DEFAULT_VALUE'_FME_NO_OP_'BOOL_OP;OR;COMPOSITE_TEST;1;TEST @Value(Ålder) < 5'1'FME_NUM_CONDITIONS2___
      SET_TO 5-15 (varchar(200)) = FME_CONDITIONAL:DEFAULT_VALUE'_FME_NO_OP_'BOOL_OP;AND;COMPOSITE_TEST;1 AND 2;TEST @Value(Ålder) >= 5;TEST @Value(Ålder) < 15'1'FME_NUM_CONDITIONS2___
      SET_TO 15-25 (varchar(200)) = FME_CONDITIONAL:DEFAULT_VALUE'_FME_NO_OP_'BOOL_OP;AND;COMPOSITE_TEST;1 AND 2;TEST @Value(Ålder) >= 15;TEST @Value(Ålder) < 25'1'FME_NUM_CONDITIONS2___
      SET_TO 25-35 (varchar(200)) = FME_CONDITIONAL:DEFAULT_VALUE'_FME_NO_OP_'BOOL_OP;AND;COMPOSITE_TEST;1 AND 2;TEST @Value(Ålder) >= 15;TEST @Value(Ålder) < 25'1'FME_NUM_CONDITIONS2___
      SET_TO 35-45 (varchar(200)) = FME_CONDITIONAL:DEFAULT_VALUE'_FME_NO_OP_'BOOL_OP;AND;COMPOSITE_TEST;1 AND 2;TEST @Value(Ålder) >= 35;TEST @Value(Ålder) < 45'1'FME_NUM_CONDITIONS2___
      SET_TO 45-55 (varchar(200)) = FME_CONDITIONAL:DEFAULT_VALUE'_FME_NO_OP_'BOOL_OP;AND;COMPOSITE_TEST;1 AND 2;TEST @Value(Ålder) >= 45;TEST @Value(Ålder) < 55'1'FME_NUM_CONDITIONS2___
      SET_TO 55-65 (varchar(200)) = FME_CONDITIONAL:DEFAULT_VALUE'_FME_NO_OP_'BOOL_OP;AND;COMPOSITE_TEST;1 AND 2;TEST @Value(Ålder) >= 55;TEST @Value(Ålder) < 65'1'FME_NUM_CONDITIONS2___
      SET_TO 65+ (varchar(200)) = FME_CONDITIONAL:DEFAULT_VALUE'_FME_NO_OP_'BOOL_OP;OR;COMPOSITE_TEST;1;TEST @Value(Ålder) >= 65'1'FME_NUM_CONDITIONS2___
    -> StatisticsCalculator
StatisticsCalculator
    CALCULATION_MODE = NUMERIC
    FEAT_STATS = Åldersgrupp,NUMERIC_MODE,,,COUNT,,,,,,,,,,;0-5,NUMERIC_MODE,,,,SUM,,,,,,,,,;5-15,NUMERIC_MODE,,,,SUM,,,,,,,,,;15-25,NUMERIC_MODE,,,,SUM,,,,,,,,,;25-35,NUMERIC_MODE,,,,SUM,,,,,,,,,;35-45,NUMERIC_MODE,,,,SUM,,,,,,,,,;45-55,NUMERIC_MODE,,,,SUM,,,,,,,,,;55-65,NUMERIC_MODE,,,,SUM,,,,,,,,,;65+,NUMERIC_MODE,,,,SUM,,,,,,,,,
    SUMMARY -> AttributeCreator_5
Note: Sätt vad som som ska synas för gruppen
AttributeCreator_5
    ATTR_TABLE:
      SET_TO text1 (varchar(200)) = FME_CONDITIONAL:DEFAULT_VALUE'_FME_NO_OP_'BOOL_OP;OR;COMPOSITE_TEST;1;TEST 65+.sum ATTRIBUTE_HAS_A_VALUE _FME_BLANK_STRING_'@Value(65+.sum) st 65+ år
        'FME_NUM_CONDITIONS2___
      SET_TO DESC (varchar(200)) = @Value(text1)@Value(55-65.sum) st 55-65 år
        @Value(45-55.sum) st 45-55 år
        @Value(35-45.sum) st 35-45 år
        @Value(25-35.sum) st 25-35 år
        @Value(15-25.sum) st 15-25 år
        @Value(5-15.sum) st 5-15 år
        @Value(0-5.sum) st 0-5 år
      SET_TO link (buffer) = https://google.se
      SET_TO layerName (varchar(50))
      SET_TO icon (buffer) = #ic_launch_24px
      SET_TO name (buffer) = Folkbokförda
      SET_TO layerTitle (varchar(200)) = @Value(Åldersgrupp.total_count) st personer folkbokförda varav
    -> GeometryFilter
AttributeExposer_2
    ATTR_TABLE = fme_feature_type,
    -> AttributeCreator_3
Note: Sätt vad som som ska synas för gruppen
AttributeCreator_3
    ATTR_TABLE:
      SET_TO DESC (varchar(200)) = @Value(beladress) är adressen
        @Value(postnr) kolla här
      SET_TO link (buffer) = https://community.safe.com/s/question/0D54Q000080h9spSAA/if-statement-in-jsontemplater
      SET_TO layerName (varchar(200)) = @Value(fme_feature_type)
      SET_TO icon (buffer) = #ic_launch_24px
      SET_TO name (buffer) = Adresser
      SET_TO layerTitle (varchar(254)) = @Value(beladress)
    -> GeometryFilter
AttributeExposer
    ATTR_TABLE = fme_feature_type,
    -> AttributeCreator_4
Note: Sätt vad som som ska synas för gruppen
AttributeCreator_4
    ATTR_TABLE:
      SET_TO DESC (varchar(200)) = @Value(blockenhet) är bra
        @Value(fastighet) är fastighet
      SET_TO link (buffer) = https://engage.safe.com/transformers/json-templater/
      SET_TO layerName (buffer) = fir_fastighet_areal_y
      SET_TO icon (buffer) = #ic_launch_24px
      SET_TO name (buffer) = Fastigheter
      SET_TO layerTitle (varchar(254)) = @Value(fastighet)
      SET_TO report_gid (number(20,0)) = @Value(gid)
    -> GeometryFilter

Bookmark: Lager som används för "Välj geometri"
ParameterFetcher_2
    ATTR_LIST = _LAYER $(LAYER)
    -> FeatureReader_3 [INITIATOR]
Note: Möjliggör annorlunda hantering av lager beroende på om välj geometri använts eller inte. T.ex. vill man endast ha vald fastighet med "Välj geometri" men alla fastigheter som intersect när man ritar geometri
Note: Fastigheter
FeatureReader_3
    ATTRIBUTES = gis.fir_fastighet_areal_y,"uuid,fastighet,blockenhet,totalar,landar,vattenar,inlagd_dat,typ,gid"
    ATTR_ACCUM_MODE = Only Use Result
    COMBINE_GEOM = Use Result
    DATASET = $(FME_SHAREDRESOURCE_DATA)\Sigtuna\gis.fir_fastighet_areal_y.shp
    FORMAT = SHAPEFILE
    INTERACT = FME_CONDITIONAL:DEFAULT_VALUE'INTERSECTS'BOOL_OP;OR;COMPOSITE_TEST;1;TEST _LAYER ATTRIBUTE_HAS_A_VALUE _FME_BLANK_STRING_'EQUALS'FME_NUM_CONDITIONS2___
    ORDER_RESULTS = No
    OUTPUT_FEATURES_DISPLAY = Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    gis.fir_fastighet_areal_y -> AttributeExposer

Bookmark: Användare lägger till datakällor här
Note: layerName = Geoservernamn / layerTitle = Rad som visas i fet stil t.ex. Fastighetsnamn / name = Rubrik på kategori t.ex. Fastighet. Lager med samma name grupperas ihop under den rubriken. / DESC = Text som visas som innehåll för objektet / link = länk / icon = Ikon som används, skrivs lika man gör i Origo t.ex. #fa-font. Anges inget används en default ikon / report_gid = primärnyckelattribut för att använda geoserver funktionalitet för att nå vektorobjekt med id
Note: Sorterar geometrier så de behandlas på rätt sätt
GeometryFilter
    FILTER_MODE = SIMPLE
    FILTER_MULTI = FILTER_TYPES]"Line Point Area Null"]FME_CONTROLLER_QUERY_FILE]]FME_CONTROLLER_CHOICE]Simple
    Null -> Aggregator
    Null -> JSONTemplater_4 [ITEM]
    Point -> GeometryExtractor
    Curve -> Clipper [CANDIDATE]
    Area -> Bufferer

Bookmark: Klipper yta för bättre hantering av stora objekt
Bufferer
    ANGLE = 22.5
    CAP_STYLE = Arc
    CORNER_STYLE = Arc
    MODE = AREA
    OFFSET = 0.001
    OFFSET_UNITS = NONE
    PRECISION = APPROX
    BUFFERED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> CenterPointReplacer

Bookmark: Tar fram geometri till json
Note: Ingång för yt- och linjegeometri
CenterPointReplacer
    POINTTYPE = INSIDE
    POINT -> GeometryExtractor
Note: Ingång för punktgeometri
GeometryExtractor
    ATTR = _geometry
    JSON_MAX_DIGITS = 7
    KIND_LONG = GeoJSON
    REMOVE_GEOMETRY = No
    -> JSONFragmenter
JSONFragmenter
    EXPLODE_FORMAT = JSON
    EXTRACT_ATTR = Yes
    JSON_ATTR = _geometry
    JSON_QUERY = json[*]
    READ_FROM_FILE = NO
    RECURSIVE = Yes
    REJECT_EMPTY_LISTS = YES
    FRAGMENTS -> Tester_2
Tester_2
    BOOL_OP = OR
    TEST_CLAUSE = TEST @Value(json_index) = coordinates
    TEST_MODE = TEST
    PASSED -> Aggregator
    PASSED -> JSONTemplater_4 [ITEM]

Bookmark: Bygger ihop json för Origo
Note: Kategorier
Aggregator
    ACCUM_ATTRS_NAME = Use Attributes From One Feature
    AGGREGATE_TYPE = Homogeneous Collection (If Possible)
    GROUP_BY = name
    MODE = Geometry - Assemble One Level
    SEP = ,
    AGGREGATE -> JSONTemplater_4 [ROOT]
Note: Kategorier med items
JSONTemplater_4
    CONSECUTIVE_GROUPS = No
    GROUP_BY = name
    ITEM_QUERY_EXPR:
      {
      "title": fme:get-attribute("layerTitle"),
      "layerName": fme:get-attribute("layerName"),
      "description": fme:get-attribute("DESC"),
      "geometry": fme:get-attribute("_geometry"),
      "link": fme:get-attribute("link"),
      "icon": fme:get-attribute("icon"),
       "gid": fme:get-attribute("report_gid")
      }
    RESULT_ATTRIBUTE = _result_category
    ROOT_QUERY_EXPR:
      {
            "name": fme:get-attribute("name"),
             "item": [
              fme:process-features("ITEM")
              ]
       }
    VISIBLE_QUERY_VALIDATE = Yes
    -> Aggregator_2
Note: Rapport
Aggregator_2
    ACCUM_ATTRS_NAME = Merge Incoming Attributes
    AGGREGATE_TYPE = Homogeneous Collection (If Possible)
    CONCAT_ATTRS = _result_category
    MODE = Geometry - Assemble One Level
    SEP = ,
    AGGREGATE -> AttributeCreator_2
Note: Rapport med category
AttributeCreator_2
    ATTR_TABLE:
      SET_TO final_json (varchar(200)) = 	{
            "title": "Byggrapport",
        	"category": [
            @Value(_result_category)
            ]
            }
      SET_TO text_line_data (varchar(200)) = @Value(final_json)
    -> text_line (writer TEXTLINE_1)
text_line (writer TEXTLINE_1)
    attributes: text_line_data buffer
